FME workspace transit_api_get_bus.fmw

Parameters:
- busId =   # Bus ID

Writers:
- TEXTLINE_1: TEXTLINE to /Users/sharper/Documents/Workspaces/output.txt

Creator
    GEOMTYPE = Geometry Object
    NUM = 1
    CREATED -> ParameterFetcher
ParameterFetcher
    ATTR_LIST = busId {$(busId)}
    -> SQLExecutor [INITIATOR]
GeometryExtractor
    ATTR = _geometry
    KIND_LONG = OGC Well Known Text
    REMOVE_GEOMETRY = No
    OGCVERSION = 1.1
    OGC_WKT_PRECISION_DISPLAY = Shortened 64-bit
    -> SuccessJSONBuilder
SuccessJSONBuilder: AttributeCreator
    ATTR_TABLE = SET_TO text_line_data = {"bus_id":"@Value(bus_id)","bearing": "@Value(bearing)","route_no":"@Value(route_no)", "speed":0, "recorded_time": "@Value(recorded_time)","geometry":"@Value(_geometry)","crs":"EPSG:4326"}
    -> text_line (writer TEXTLINE_1)
ValidBusNoJSONBuilde: AttributeCreator
    ATTR_TABLE = SET_TO text_line_data = {"status":400,"message": "Invalid Attribute: The bus ID does not match an existing ID"}
    -> text_line (writer TEXTLINE_1)
text_line (writer TEXTLINE_1)
    attributes: text_line_data buffer

Bookmark: Check for valid BUS ID that exists
SQLExecutor
    POSTGIS_QUERY_FEATURE_TYPES_FOR_MERGE_FILTERS = Yes
    COMBINE_ATTRS = Keep Result Attributes if Conflict
    FORMAT = POSTGIS
    COMBINE_GEOM = Initiator Geometry Only
    POSTGIS_SCHEMAS_FOR_TABLE_LISTING = transit
    POSTGIS_DISABLE_COLLECTION_SPLITTING = yes
    POSTGIS_NAMED_CONNECTION = FMEpedia
    POSTGIS_USE_TRUE_POSTGIS_TYPES = yes
    EXPOSED_ATTRIBUTE_LIST = bus_count
    DATASET = FMEpedia
    SQL_STATEMENT = SELECT count(bus_id) As bus_count FROM "transit"."Buses" WHERE bus_id = '@Value(busId)';
    RESULT -> TestBusIdExists
TestBusIdExists: Tester
    TEST_MODE = Automatic
    TEST_DESCRIPTION = ""
    TEST_CLAUSE = TEST @Value(bus_count) != 0
    BOOL_OP = OR
    PASSED -> FeatureReader [INITIATOR]
    FAILED -> ValidBusNoJSONBuilde
FeatureReader
    POSTGIS_DISABLE_COLLECTION_SPLITTING = yes
    ATTRIBUTES = transit.Buses,"bus_id,route_no,recorded_time,bearing,speed"
    POSTGIS_USE_TRUE_POSTGIS_TYPES = yes
    POSTGIS_CLIP_TO_ENVELOPE = NO
    POSTGIS_SCHEMAS_FOR_TABLE_LISTING = transit
    OUTPUT_FEATURES_DISPLAY = Data Features
    POSTGIS_NAMED_CONNECTION = FMEpedia
    FORMAT = POSTGIS
    DATASET = FMEpedia
    FEATURETYPES = transit.Buses
    ATTR_ACCUM_MODE = Merge Initiator and Result
    POSTGIS_QUERY_FEATURE_TYPES_FOR_MERGE_FILTERS = Yes
    INTERACT = <No Spatial Filter>
    POSTGIS_USE_SEARCH_ENVELOPE = NO
    WHERE = bus_id='@Value(busId)'
    ATTR_CONFLICT_RES = Use Result
    COMBINE_GEOM = Use Result
    transit.Buses -> GeometryExtractor
