FME workspace transit_api_update_bus.fmw

Parameters:
- longitude = -123.102837   # Longitude
- latitude = 49.236620   # Latitude
- busId = 2fa02eda-3703-11e6-b566-12c0fde69e4d   # bus_id
- route_no = 20

Writers:
- TEXTLINE_1: TEXTLINE to /Users/sharper/Documents/Workspaces/output.txt

text_line (writer TEXTLINE_1)
    attributes: text_line_data buffer

Bookmark: Read parameters and check for existing attributes
Creator
    GEOMTYPE = Geometry Object
    NUM = 1
    CREATED -> ParameterFetcher
ParameterFetcher
    ATTR_LIST = bus_id {$(busId)} latitude {$(latitude)} longitude {$(longitude)} route_no {$(route_no)}
    -> TestForValidCoordinates
TestForValidCoordinates: Tester
    TEST_DESCRIPTION = ""
    TEST_CLAUSE:
      TEST @Value(latitude) RANGE [-90,90]
      TEST @Value(longitude) RANGE [-180,180]
    TEST_MODE = Automatic
    BOOL_OP = AND
    PASSED -> TestForValidBusId
    FAILED -> InvalidCoordinatesJSONBuilder
TestForValidBusId: Tester
    TEST_DESCRIPTION = ""
    TEST_CLAUSE = TEST bus_id NOT_ATTRIBUTE_IS_EMPTY ""
    TEST_MODE = Automatic
    BOOL_OP = AND
    PASSED -> TestForValidRouteNo
    FAILED -> BusNoJSONBuilder
TestForValidRouteNo: Tester
    TEST_DESCRIPTION = ""
    TEST_CLAUSE = TEST route_no NOT_ATTRIBUTE_IS_EMPTY ""
    TEST_MODE = Automatic
    BOOL_OP = AND
    PASSED -> SQLExecutor [INITIATOR]
    FAILED -> RouteNoJSONBuilder

Bookmark: Error messages
InvalidCoordinatesJSONBuilder: AttributeCreator
    ATTR_TABLE = SET_TO text_line_data = {"status":400,"message": "Invalid coordinates. Latitude measurements should range from -90 to 90, longitude should range from -180 to 180."}
    -> text_line (writer TEXTLINE_1)
BusNoJSONBuilder: AttributeCreator
    ATTR_TABLE = SET_TO text_line_data = {"status":400,"message": "Missing attribute: The bus ID cannot be blank."}
    -> text_line (writer TEXTLINE_1)
RouteNoJSONBuilder: AttributeCreator
    ATTR_TABLE = SET_TO text_line_data = {"status":400,"message": "Missing attribute: The route number cannot be blank."}
    -> text_line (writer TEXTLINE_1)
ValidBusNoJSONBuilde: AttributeCreator
    ATTR_TABLE = SET_TO text_line_data = {"status":400,"message": "Invalid Attribute: The bus ID does not match an existing ID"}
    -> text_line (writer TEXTLINE_1)
NoFeaturesWrittenJSONBuilder: AttributeCreator
    ATTR_TABLE = SET_TO text_line_data = {"status":500,"message": "Internal server error. Data was not written to the database."}
    -> text_line (writer TEXTLINE_1)
SuccessJSONBuilder: AttributeCreator
    ATTR_TABLE = SET_TO text_line_data = {"status":201,"message": "Data successfully updated."}
    -> text_line (writer TEXTLINE_1)

Bookmark: Check for valid BUS ID that exists
SQLExecutor
    FORMAT = POSTGIS
    DATASET = FMEpedia
    POSTGIS_NAMED_CONNECTION = FMEpedia
    POSTGIS_QUERY_FEATURE_TYPES_FOR_MERGE_FILTERS = Yes
    COMBINE_GEOM = Initiator Geometry Only
    POSTGIS_SCHEMAS_FOR_TABLE_LISTING = transit
    POSTGIS_USE_TRUE_POSTGIS_TYPES = yes
    SQL_STATEMENT:
      SELECT count(bus_id) As bus_count
      FROM "transit"."Buses"
      WHERE bus_id = '@Value(bus_id)';
    EXPOSED_ATTRIBUTE_LIST = bus_count
    COMBINE_ATTRS = Keep Result Attributes if Conflict
    POSTGIS_DISABLE_COLLECTION_SPLITTING = yes
    RESULT -> TestBusIdExists
TestBusIdExists: Tester
    TEST_DESCRIPTION = ""
    TEST_CLAUSE = TEST @Value(bus_count) != 0
    TEST_MODE = Automatic
    BOOL_OP = OR
    PASSED -> TimeStamper
    PASSED -> FeatureReader [INITIATOR]
    FAILED -> ValidBusNoJSONBuilde

Bookmark: Create Geometry
TimeStamper
    TIME_ATTR = recorded_time
    FMT = ISO DateTime (^Y-^m-^dT^H:^M:^S)
    -> VertexCreator
VertexCreator
    YVAL = @Value(latitude)
    MODE_NAME = Add Point
    XVAL = @Value(longitude)
    -> CoordinateSystemSetter
CoordinateSystemSetter
    COORDSYS = EPSG:4326
    -> FromToBuilder [TO]
    -> FeatureMerger [REQUESTOR]

Bookmark: Calculate line and calculate bearing
FeatureReader
    POSTGIS_QUERY_FEATURE_TYPES_FOR_MERGE_FILTERS = Yes
    POSTGIS_SCHEMAS_FOR_TABLE_LISTING = transit
    POSTGIS_USE_TRUE_POSTGIS_TYPES = yes
    ATTRIBUTES = transit.Buses,"bus_id,route_no,recorded_time,bearing,speed"
    OUTPUT_FEATURES_DISPLAY = Schema and Data Features
    POSTGIS_CLIP_TO_ENVELOPE = NO
    POSTGIS_USE_SEARCH_ENVELOPE = NO
    COMBINE_GEOM = Use Result
    POSTGIS_DISABLE_COLLECTION_SPLITTING = yes
    WHERE = bus_id = '@Value(bus_id)'
    POSTGIS_NAMED_CONNECTION = FMEpedia
    FORMAT = POSTGIS
    FEATURETYPES = transit.Buses
    INTERACT = <No Spatial Filter>
    DATASET = FMEpedia
    ATTR_ACCUM_MODE = Only Use Result
    transit.Buses -> FromToBuilder [FROM]
FromToBuilder
    REFERATTR = bus_id
    REFEEATTR = bus_id
    FROM-TO -> AzimuthCalculator [Line]
AzimuthCalculator
    -> AttributeRangeMapper
AttributeRangeMapper
    OUT_ATTR = bearing
    LUT = 0,22.5,N,22.6,67.5,NE,67.6,112.5,E,112.6,157.5,SE,157.6,179.9,S,-180,-157.5,S,-157.4,-112.5,SW,-112.4,-67.5,W,-67.4,-22.5,NW,-22.4,0,N,,,
    IN_ATTR = acAzimuth
    -> FeatureMerger [SUPPLIER]

Bookmark: Prepare and write the data
FeatureMerger
    ATTR_CONFLICT_RES = Use Requestor
    PROCESS_DUPS = No
    SUPPLIERS_FIRST = No
    MERGE_TYPE = Attributes Only
    JOIN_KEYS = "    AUTO"
    ATTR_ACCUM_MODE = Merge Supplier
    IGNORE_NULLS = No
    REJECT_NULL_MISSING_KEYS = No
    MERGED -> FeatureWriter [transit.Buses]
FeatureWriter
    WRITER_DIRECTIVES = NAMED_CONNECTION,FMEpedia,LOWERCASE_ATTRIBUTE_NAMES,Yes,SPATIAL_COLUMN_TYPE,geometry,COORDINATE_SYSTEM_GRANULARITY,FEATURE_TYPE,SPATIAL_COLUMN_NAME,geom
    POSTGIS_COORDINATE_SYSTEM_GRANULARITY = FEATURE_TYPE
    POSTGIS_SPATIAL_COLUMN_NAME = geom
    FEATURE_TYPE_LIST_ATTR = _feature_type
    DATASET_ATTR = _dataset
    TOTAL_FEATURES_WRITTEN_ATTR = _total_features_written
    DATASET = FMEpedia
    POSTGIS_LOWERCASE_ATTRIBUTE_NAMES = Yes
    POSTGIS_NAMED_CONNECTION = FMEpedia
    FORMAT = POSTGIS
    POSTGIS_SPATIAL_COLUMN_TYPE = geometry
    SUMMARY -> TestWrittenFeatures
TestWrittenFeatures: Tester
    TEST_DESCRIPTION = ""
    TEST_CLAUSE = TEST @Value(_total_features_written) NOT_= 0
    TEST_MODE = Automatic
    BOOL_OP = AND
    PASSED -> SuccessJSONBuilder
    FAILED -> NoFeaturesWrittenJSONBuilder

FME custom transformer LoopFilter
Tests whether a line is a loop, i.e. whether start and end coordinates match.
The transformers outputs loops through PASSED port, and non-loops through FAILED port.

LINE (input)
    -> LineFilter
LineFilter: GeometryFilter
    BREAK_AGG = No
    GEOM_PORT_NAMES = Line
    LINE -> CoordinateExtractor
CoordinateExtractor
    Y_ATTR = _y1
    IND = 0
    MODE = Specify Coordinate
    X_ATTR = _x1
    Z_ATTR = _z1
    -> CoordinateExtractor_2
CoordinateExtractor_2
    Y_ATTR = _y2
    IND = -1
    MODE = Specify Coordinate
    X_ATTR = _x2
    Z_ATTR = _z2
    -> ExpressionEvaluator
ExpressionEvaluator
    ACTION = Create New Attribute
    VAL_ATTR = _isLoop
    EXPRESSION = (@Value(_x1)-@Value(_x2))||(@Value(_y1)-@Value(_y2))
    -> Tester
Tester
    TEST_LIST = &_isLoop,=,0
    TEST_DESCRIPTION = ""
    TEST_CLAUSE = TEST @Value(_isLoop) = 0
    TEST_MODE = Automatic
    BOOL_OP = OR
    PASSED -> AttributeRemover
    FAILED -> AttributeRemover_2
AttributeRemover
    REMOVE_ATTRS = _z1,_z2,_y1,_y2,_isLoop,_x1,_x2
    -> PASSED (output)
PASSED (output)
AttributeRemover_2
    REMOVE_ATTRS = _z1,_z2,_y1,_y2,_isLoop,_x1,_x2
    -> FAILED (output)
FAILED (output)

FME custom transformer FromToBuilder
Creates From-To lines for the ShortestPathFinder transformer.
From FME 2013, the ShortestPathFinder transformer has added support for 1:m, m:1, and m:m relationships between source and destination points. To use the new ShortestPathFinder, you need to have lines that connect the source (From) to the destination (To) points you want the transformer to check. The FromToBuilder custom transformer helps you create these From-To lines that can be used by the ShortestPathFinder.
The "FROM" input port accepts points and lines. If a line is entered via this port, its first vertex will be considered as the source point and all its other vertices will be used as intermedite stops. The "TO" port only accepts points. These points represent the destinations.
For each FROM and TO pair of inputs that have the same join attribute, one FROM-TO line is produced.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- REFERATTR =   # " " FROM Join Attribute
- REFEEATTR =   # " " TO Join Attribute

FROM (input)
    -> GeometryFilter_2
Note: Only points and lines are accepted
GeometryFilter_2
    BREAK_AGG = No
    POINT -> FeatureMerger [REQUESTOR]
    LINE -> FeatureMerger [REQUESTOR]
TO (input)
    -> GeometryFilter
Note: Only points are accepted
GeometryFilter
    BREAK_AGG = No
    POINT -> CoordinateExtractor
Note: Extract the coordinates / of each "To" point
CoordinateExtractor
    Y_ATTR = ___y
    Z_DEFAULT = -9999
    IND = 0
    X_ATTR = ___x
    -> FeatureMerger [SUPPLIER]
Note: Add the attributes of "To" features to / their corresponding "From" features
FeatureMerger
    BUILD_INCOMPLETE = No
    REFERATTR = $(REFERATTR)
    REFEEATTR = $(REFEEATTR)
    MERGE_TYPE = Attributes Only
    PROCESS_DUPS = Yes
    COMPLETE -> 2DPointAdder
    INCOMPLETE -> <REJECTED> (output)
    EMPTY -> <REJECTED> (output)
    UNREFERENCED -> <REJECTED> (output)
    DUPLICATE_SUPPLIER -> <REJECTED> (output)
Note: Add "To" points / to their "From" features
2DPointAdder
    XVALATTR = @Value(___x)
    YVALATTR = @Value(___y)
    -> AttributeRemover
Note: Clean up
AttributeRemover
    REMOVE_ATTRS = ___x,___y
    -> FROM-TO (output)
FROM-TO (output)
<REJECTED> (output)

FME custom transformer AzimuthCalculator
Calculates the angle and azimuth of a line or a polyline. The azimuth is the angle between the line and the north vector. Angles are measured from the reference point of east (which represents 0 degrees).
Note: For polylines it returns the angle and azimuth of a line connecting the first and the last vertices of the polyline. For retrieving information about each segment of the polyline use PolylineAnalyzer.
Input Ports 
    Input
Input features must contain valid line geometry. 
    Output Ports
    Output
Features are output with new attributes containing the angle and azimuth of the line or polyline. 
    acAngle: Angles increase counterclockwise from the reference point of east (which represents zero degrees).
    acAzimuth: The azimuth value can range from -180 to 180 with north as 0, south as -180, east as 90, and west as -90. 
    <Rejected>
Any features that are not valid line geometry, or are loops (coincident start and end points), will be passed through this port. Rejected features are output with value INVALID_GEOMETRY_TYPE stored in the fme_rejection_code attribute.
    Parameters 
This transformer has no parameters.

Line (input)
    -> GeometryFilter
Note: Removes all intermediate attributes
ATTRIBUTEREMOVER: AttributeRemover
    REMOVE_ATTRS = acX2,acZ1,acZ2,acY1,acY2,acX1
    -> Output (output)
Output (output)
AttributeCreator
    ATTR_TABLE = SET_TO fme_rejection_code = INVALID_GEOMETRY_TYPE
    -> <Rejected> (output)
<Rejected> (output)

Bookmark: Input Filter
  Sorts out all unsuitable features - non linear, and loops.
Note: Passes only lines to / the next transfomer
GeometryFilter
    BREAK_AGG = No
    GEOM_PORT_NAMES = Line
    LINE -> LoopFilter [LINE]
    <UNFILTERED> -> AttributeCreator
Note: Tests whether a / line is a loop
LoopFilter
    PASSED -> LOGGER
    FAILED -> COORDINATEFETCHER
LOGGER: Logger
    MAXCOORDS = 3
    MAXFEATS = 20
    MESSAGE = Feature is a loop
    LOGGED -> AttributeCreator

Bookmark: Angle Calculations
COORDINATEFETCHER: CoordinateExtractor
    Y_ATTR = acY1
    Z_DEFAULT = -9999
    IND = 0
    MODE = Specify Coordinate
    X_ATTR = acX1
    Z_ATTR = acZ1
    -> COORDINATEFETCHER_2
COORDINATEFETCHER_2: CoordinateExtractor
    Y_ATTR = acY2
    Z_DEFAULT = -9999
    IND = -1
    MODE = Specify Coordinate
    X_ATTR = acX2
    Z_ATTR = acZ2
    -> EXPRESSIONEVALUATOR
EXPRESSIONEVALUATOR: ExpressionEvaluator
    ACTION = Create New Attribute
    VAL_ATTR = acAngle
    EXPRESSION = acos((@Value(acX2)-@Value(acX1))/sqrt(pow((@Value(acY2)-@Value(acY1)),2) + pow((@Value(acX2)-@Value(acX1)),2)))* (180/3.1415926535897932)
    -> EXPRESSIONEVALUATOR_2
EXPRESSIONEVALUATOR_2: ExpressionEvaluator
    ACTION = Create New Attribute
    VAL_ATTR = acAngle
    EXPRESSION = ((@Value(acY2)-@Value(acY1))<0)?(360-@Value(acAngle)):(@Value(acAngle))
    -> TESTER

Bookmark: Azimuth Calculations
  Testers check quadrand, and calculate the Azimuth Accordingly
TESTER: Tester
    TEST_LIST = &acAngle,>,90
    TEST_DESCRIPTION = ""
    TEST_CLAUSE = TEST @Value(acAngle) > 90
    TEST_MODE = Automatic
    BOOL_OP = OR
    PASSED -> TESTER_2
    FAILED -> EXPRESSIONEVALUATOR_4
TESTER_2: Tester
    TEST_LIST = &acAngle,""">""",270
    TEST_DESCRIPTION = ""
    TEST_CLAUSE = TEST @Value(acAngle) > 270
    TEST_MODE = Automatic
    BOOL_OP = OR
    PASSED -> EXPRESSIONEVALUATOR_3
    FAILED -> EXPRESSIONEVALUATOR_4
EXPRESSIONEVALUATOR_3: ExpressionEvaluator
    ACTION = Create New Attribute
    VAL_ATTR = acAzimuth
    EXPRESSION = 450 - @Value(acAngle)
    -> ATTRIBUTEREMOVER
EXPRESSIONEVALUATOR_4: ExpressionEvaluator
    ACTION = Create New Attribute
    VAL_ATTR = acAzimuth
    EXPRESSION = 90 - @Value(acAngle)
    -> ATTRIBUTEREMOVER
